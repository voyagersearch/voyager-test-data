FME workspace easyTranslator.fmw
Title: Generic format translator

Parameters:
- SourceDataset_GENERIC =   # Source File
- SourceFormat = GUESS_FROM_EXTENSION
- COORDSYS =
- GENERIC_OUT_BASE_NAME_GENERIC = translated_data   # Destination Filename
- DestinationFormat = ACAD
- COORDSYS_dest =

Readers:
- GENERIC_1: GENERIC from $(SourceDataset_GENERIC) in $(COORDSYS)

Writers:
- GENERIC_2: GENERIC to D:/apps/FMEServer//DefaultResults in $(COORDSYS_dest)

Note: This Reader feature type's Merge Parameters are / configured so that all feature types send their / features through this feature type regardless of name.
Note: The Generic Reader allows you / to specify a file to read as well / as the format or it will attempt to / guess the format used by the file.
generic (reader GENERIC_1)
    -> DYNAMIC (writer GENERIC_2)
Note: This Writer feature type's Dynamic Parameters are / configured so that at run time the feature type's / schema is determined from the source file.
Note: The Generic Writer allows you to / specify an output format for the / destination file.
DYNAMIC (writer GENERIC_2)
